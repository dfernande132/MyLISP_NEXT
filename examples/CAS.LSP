; ===========================================================
; CAS01 - Capitulo 1: Representacion y abstraccion de datos
; ===========================================================
; ** PREDICADOS DE CLASIFICACION **
(DEFUN ISCONST? (E) (NUMBERP E))
(DEFUN ISVAR? (E) (SYMBOLP E))
(DEFUN ISSUM? (E)
  (AND (LISTP E) (EQ (CAR E) '+)))
(DEFUN ISPROD? (E)
  (AND (LISTP E) (EQ (CAR E) '*)))
(DEFUN ISPOW? (E)
  (AND (LISTP E) (EQ (CAR E) 'POT)))
; ** SELECTORES **
(DEFUN ADDEND (E) (CAR (CDR E)))
(DEFUN AUGEND (E) (CAR (CDR (CDR E))))
(DEFUN FACTOR1 (E) (CAR (CDR E)))
(DEFUN FACTOR2 (E) (CAR (CDR (CDR E))))
(DEFUN BASE (E) (CAR (CDR E)))
(DEFUN EXPON (E) (CAR (CDR (CDR E))))
; ** CONSTRUCTORES (version inteligente, actualizados en Capitulo 4) **
(DEFUN CERO? (X) (AND (ISCONST? X) (= X 0)))
(DEFUN UNO?  (X) (AND (ISCONST? X) (= X 1)))
(DEFUN MAKESUM (A1 A2)
  (COND ((CERO? A1) A2)
        ((CERO? A2) A1)
        ((AND (ISCONST? A1) (ISCONST? A2)) (+ A1 A2))
        (T (LIST '+ A1 A2))))
(DEFUN MAKEPROD (A1 A2)
  (COND ((OR (CERO? A1) (CERO? A2)) 0)
        ((UNO? A1) A2)
        ((UNO? A2) A1)
        ((AND (ISCONST? A1) (ISCONST? A2)) (* A1 A2))
        (T (LIST '* A1 A2))))
(DEFUN MAKEPOW (B E)
  (COND ((CERO? E) 1)
        ((UNO? E) B)
        ((UNO? B) 1)
        ((AND (ISCONST? B) (ISCONST? E)) (POTENCIA B E))
        (T (LIST 'POT B E))))
; ===========================================================
; CAS02 - Capitulo 2: Sustitucion (SUBST) y evaluacion numerica
; ===========================================================
(DEFUN SUBST (E VBL VAL)
  (COND ((ISCONST? E) E)
        ((ISVAR? E)
         (COND ((EQ E VBL) VAL)
               (T E)))
        ((ISSUM? E)
         (MAKESUM (SUBST (ADDEND E) VBL VAL)
                   (SUBST (AUGEND E) VBL VAL)))
        ((ISPROD? E)
         (MAKEPROD (SUBST (FACTOR1 E) VBL VAL)
                    (SUBST (FACTOR2 E) VBL VAL)))
        ((ISPOW? E)
         (MAKEPOW (SUBST (BASE E) VBL VAL)
                   (SUBST (EXPON E) VBL VAL)))))
(DEFUN LIBRE? (X) (EQ X 'VARLIBRE))
(DEFUN POTENCIA (B N)
  (COND ((= N 0) 1)
        (T (* B (POTENCIA B (- N 1))))))
(DEFUN EVALSUMA (E)
  (LET ((A (EVALEXPR (ADDEND E))))
    (COND ((LIBRE? A) A)
          (T (LET ((B (EVALEXPR (AUGEND E))))
               (COND ((LIBRE? B) B)
                     (T (+ A B))))))))
(DEFUN EVALPROD (E)
  (LET ((A (EVALEXPR (FACTOR1 E))))
    (COND ((LIBRE? A) A)
          (T (LET ((B (EVALEXPR (FACTOR2 E))))
               (COND ((LIBRE? B) B)
                     (T (* A B))))))))
(DEFUN EVALPOW (E)
  (LET ((B (EVALEXPR (BASE E))))
    (COND ((LIBRE? B) B)
          (T (LET ((N (EVALEXPR (EXPON E))))
               (COND ((LIBRE? N) N)
                     (T (POTENCIA B N))))))))
(DEFUN EVALEXPR (E)
  (COND ((ISCONST? E) E)
        ((ISVAR? E)
         (PROGN (PRINT "CAS: variable libre, no evaluable:")
                (PRINT E)
                'VARLIBRE))
        ((ISSUM? E) (EVALSUMA E))
        ((ISPROD? E) (EVALPROD E))
        ((ISPOW? E) (EVALPOW E))))
; ===========================================================
; CAS03 - Capitulo 3: Derivacion simbolica cruda (DERIV)
; ===========================================================
(DEFUN DSUMA (E VBL)
  (MAKESUM (DERIV (ADDEND E) VBL) (DERIV (AUGEND E) VBL)))
(DEFUN DPROD (E VBL)
  (MAKESUM (MAKEPROD (DERIV (FACTOR1 E) VBL) (FACTOR2 E))
            (MAKEPROD (FACTOR1 E) (DERIV (FACTOR2 E) VBL))))
(DEFUN DPOW (E VBL)
  (MAKEPROD (MAKEPROD (EXPON E) (MAKEPOW (BASE E) (- (EXPON E) 1)))
             (DERIV (BASE E) VBL)))
(DEFUN DERIV (E VBL)
  (COND ((ISCONST? E) 0)
        ((ISVAR? E) (COND ((EQ E VBL) 1) (T 0)))
        ((ISSUM? E) (DSUMA E VBL))
        ((ISPROD? E) (DPROD E VBL))
        ((ISPOW? E) (DPOW E VBL))))
; ===========================================================
; CAS05 - Capitulo 5: Orden canonico y terminos semejantes
; ===========================================================
(DEFUN COEF (E)
  (COND ((ISCONST? E) E)
        ((ISPROD? E)
         (COND ((ISCONST? (FACTOR1 E)) (FACTOR1 E))
               ((ISCONST? (FACTOR2 E)) (FACTOR2 E))
               (T 1)))
        (T 1)))
(DEFUN LITERAL (E)
  (COND ((ISCONST? E) 1)
        ((ISPROD? E)
         (COND ((ISCONST? (FACTOR1 E)) (FACTOR2 E))
               ((ISCONST? (FACTOR2 E)) (FACTOR1 E))
               (T E)))
        (T E)))
(DEFUN FLATSUM (E)
  (COND ((ISSUM? E)
         (APPEND (FLATSUM (ADDEND E)) (FLATSUM (AUGEND E))))
        (T (LIST E))))
(DEFUN ASSOCADD (LIT CF ALIST)
  (COND ((NULL ALIST) (LIST (CONS LIT CF)))
        ((EQUAL (CAR (CAR ALIST)) LIT)
         (CONS (CONS LIT (+ (CDR (CAR ALIST)) CF)) (CDR ALIST)))
        (T (CONS (CAR ALIST) (ASSOCADD LIT CF (CDR ALIST))))))
(DEFUN AGRUPA (TERMS)
  (COND ((NULL TERMS) NIL)
        (T (ASSOCADD (LITERAL (CAR TERMS))
                       (COEF (CAR TERMS))
                       (AGRUPA (CDR TERMS))))))
(DEFUN REBUILD (ALIST)
  (COND ((NULL ALIST) 0)
        (T (MAKESUM (MAKEPROD (CDR (CAR ALIST)) (CAR (CAR ALIST)))
                      (REBUILD (CDR ALIST))))))
(DEFUN SIMPSUM (E) (REBUILD (ORDENA (AGRUPA (FLATSUM E)))))
; ===========================================================
; CAS06 - Capitulo 6: Simplificacion de arbol completo (SIMP)
; ===========================================================
(DEFUN SIMP (E)
  (COND ((ISCONST? E) E)
        ((ISVAR? E) E)
        ((ISSUM? E)
         (SIMPSUM (MAKESUM (SIMP (ADDEND E)) (SIMP (AUGEND E)))))
        ((ISPROD? E)
         (SIMPPROD (MAKEPROD (SIMP (FACTOR1 E)) (SIMP (FACTOR2 E)))))
        ((ISPOW? E)
         (MAKEPOW (SIMP (BASE E)) (SIMP (EXPON E))))))
; ===========================================================
; CAS07 - Capitulo 7: Simplificador de productos (SIMPPROD)
; ===========================================================
(DEFUN BASEOF (E) (COND ((ISPOW? E) (BASE E)) (T E)))
(DEFUN EXPOF  (E) (COND ((ISPOW? E) (EXPON E)) (T 1)))
(DEFUN FLATPROD (E)
  (COND ((ISPROD? E)
         (APPEND (FLATPROD (FACTOR1 E)) (FLATPROD (FACTOR2 E))))
        (T (LIST E))))
(DEFUN NUMPROD (TERMS)
  (COND ((NULL TERMS) 1)
        ((ISCONST? (CAR TERMS)) (* (CAR TERMS) (NUMPROD (CDR TERMS))))
        (T (NUMPROD (CDR TERMS)))))
(DEFUN SYMTERMS (TERMS)
  (COND ((NULL TERMS) NIL)
        ((ISCONST? (CAR TERMS)) (SYMTERMS (CDR TERMS)))
        (T (CONS (CAR TERMS) (SYMTERMS (CDR TERMS))))))
(DEFUN ADDBASE (B EXP ALIST)
  (COND ((NULL ALIST) (LIST (CONS B EXP)))
        ((EQUAL (CAR (CAR ALIST)) B)
         (CONS (CONS B (+ (CDR (CAR ALIST)) EXP)) (CDR ALIST)))
        (T (CONS (CAR ALIST) (ADDBASE B EXP (CDR ALIST))))))
(DEFUN AGRUPAP (TERMS)
  (COND ((NULL TERMS) NIL)
        (T (ADDBASE (BASEOF (CAR TERMS))
                      (EXPOF (CAR TERMS))
                      (AGRUPAP (CDR TERMS))))))
(DEFUN REBUILDP (ALIST)
  (COND ((NULL ALIST) 1)
        (T (MAKEPROD (MAKEPOW (CAR (CAR ALIST)) (CDR (CAR ALIST)))
                       (REBUILDP (CDR ALIST))))))
(DEFUN SIMPPROD (E)
  (LET ((TERMS (FLATPROD E)))
    (MAKEPROD (NUMPROD TERMS)
               (REBUILDP (ORDENA (AGRUPAP (SYMTERMS TERMS)))))))
; ===========================================================
; CAS08 - Capitulo 8: Orquestador (DERIVA y DERIVAEN)
; ===========================================================
(DEFUN DERIVA (E VBL) (SIMP (DERIV E VBL)))
(DEFUN DERIVAEN (E VBL VAL) (EVALEXPR (SUBST (DERIVA E VBL) VBL VAL)))
; ===========================================================
; CAS09 - Capitulo 9: Orden canonico estable (EXPLESS?)
; ===========================================================
(DEFUN TIPORDEN (E)
  (COND ((ISCONST? E) 0)
        ((ISVAR? E) 1)
        (T 2)))
(DEFUN EXPLESS? (E1 E2)
  (COND ((< (TIPORDEN E1) (TIPORDEN E2)) T)
        ((> (TIPORDEN E1) (TIPORDEN E2)) NIL)
        ((ISCONST? E1) (< E1 E2))
        ((ISVAR? E1) (STR< E1 E2))
        (T NIL)))
(DEFUN INSERTA (PAR LISTA)
  (COND ((NULL LISTA) (LIST PAR))
        ((EXPLESS? (CAR PAR) (CAR (CAR LISTA))) (CONS PAR LISTA))
        (T (CONS (CAR LISTA) (INSERTA PAR (CDR LISTA))))))
(DEFUN ORDENA (LISTA)
  (COND ((NULL LISTA) NIL)
        (T (INSERTA (CAR LISTA) (ORDENA (CDR LISTA))))))
; ===========================================================
; CAS10 - Capitulo 10: Impresion infija (PRINTMAT)
; ===========================================================
(DEFUN PRECOP (E)
  (COND ((ISPOW? E) 3)
        ((ISPROD? E) 2)
        ((ISSUM? E) 1)
        (T 4)))
(DEFUN ENVOLVER (E S MINIMA)
  (COND ((< (PRECOP E) MINIMA) (STRCAT "(" (STRCAT S ")")))
        (T S)))
(DEFUN NEGTERM? (E)
  (COND ((ISCONST? E) (< E 0))
        ((ISPROD? E)
         (COND ((ISCONST? (FACTOR1 E)) (< (FACTOR1 E) 0))
               ((ISCONST? (FACTOR2 E)) (< (FACTOR2 E) 0))
               (T NIL)))
        (T NIL)))
(DEFUN NEGAR (E)
  (COND ((ISCONST? E) (- E))
        ((ISPROD? E)
         (COND ((ISCONST? (FACTOR1 E))
                (MAKEPROD (- (FACTOR1 E)) (FACTOR2 E)))
               ((ISCONST? (FACTOR2 E))
                (MAKEPROD (FACTOR1 E) (- (FACTOR2 E))))
               (T E)))
        (T E)))
(DEFUN INFBASE (B) (INFIJO B 4))
(DEFUN INFPROD (E)
  (COND ((ISCONST? (FACTOR1 E))
         (COND ((= (FACTOR1 E) -1) (STRCAT "-" (INFIJO (FACTOR2 E) 2)))
               (T (STRCAT (FACTOR1 E) (INFIJO (FACTOR2 E) 2)))))
        ((ISCONST? (FACTOR2 E))
         (COND ((= (FACTOR2 E) -1) (STRCAT "-" (INFIJO (FACTOR1 E) 2)))
               (T (STRCAT (FACTOR2 E) (INFIJO (FACTOR1 E) 2)))))
        (T (STRCAT (INFIJO (FACTOR1 E) 2)
                     (STRCAT "*" (INFIJO (FACTOR2 E) 2))))))
(DEFUN INFSUMA (E)
  (COND ((NEGTERM? (AUGEND E))
         (STRCAT (INFIJO (ADDEND E) 1)
                  (STRCAT " - " (INFIJO (NEGAR (AUGEND E)) 1))))
        (T (STRCAT (INFIJO (ADDEND E) 1)
                     (STRCAT " + " (INFIJO (AUGEND E) 1))))))
(DEFUN INFIJO (E MINIMA)
  (COND ((ISCONST? E) (STRCAT E ""))
        ((ISVAR? E) (STRCAT E ""))
        ((ISPOW? E)
         (ENVOLVER E
                    (STRCAT (INFBASE (BASE E))
                             (STRCAT "^" (INFIJO (EXPON E) 3)))
                    MINIMA))
        ((ISPROD? E) (ENVOLVER E (INFPROD E) MINIMA))
        ((ISSUM? E) (ENVOLVER E (INFSUMA E) MINIMA))))
(DEFUN PRINTMAT (E) (PROGN (DISPLAY (INFIJO E 0)) (NEWLINE)))
